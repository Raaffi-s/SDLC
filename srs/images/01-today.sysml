package PlanoraToday {
    part def TodayScreen {
        part header;
        part navigation;
        part dateSummary;
        part taskList;
        part upcomingEvents;
        part quickAdd;
    }
}

package PlanoraTasks {
    part def TasksScreen {
        part header;
        part navigation;
        part searchField;
        part statusFilters;
        part taskList;
        part createTaskAction;
    }
}

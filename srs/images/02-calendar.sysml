package PlanoraCalendar {
    part def CalendarScreen {
        part header;
        part navigation;
        part monthSelector;
        part calendarGrid;
        part selectedDayAgenda;
        part createEventAction;
    }
}

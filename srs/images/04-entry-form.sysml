package PlanoraEntryForm {
    part def EntryFormScreen {
        part header;
        part entryTypeSelector;
        part titleField;
        part descriptionField;
        part dateTimeFields;
        part reminderSelector;
        part saveAction;
        part cancelAction;
    }
}
